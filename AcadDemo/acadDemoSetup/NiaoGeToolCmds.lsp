;; Implementation file that defines the application commands.
;(command "mycui" "")
(defun C:MyCommand1 ()
  (alert "Hello from 111!")
  (princ)
)

(defun C:MyCommand2 ()
  (alert "Hello from 222!")
  (princ)
)

(princ)

;;;-----BEGIN-SIGNATURE-----
;;; YAcAADCCB1wGCSqGSIb3DQEHAqCCB00wggdJAgEBMQ8wDQYJKoZIhvcNAQELBQAw
;;; CwYJKoZIhvcNAQcBoIIFZDCCBWAwggRIoAMCAQICDyWu/I85IOePf6JKs6J90TAN
;;; BgkqhkiG9w0BAQsFADB9MQswCQYDVQQGEwJHQjEbMBkGA1UECBMSR3JlYXRlciBN
;;; YW5jaGVzdGVyMRAwDgYDVQQHEwdTYWxmb3JkMRowGAYDVQQKExFDT01PRE8gQ0Eg
;;; TGltaXRlZDEjMCEGA1UEAxMaQ09NT0RPIFJTQSBDb2RlIFNpZ25pbmcgQ0EwHhcN
;;; MTgwMjIzMDAwMDAwWhcNMjAwMjIzMjM1OTU5WjCBqTELMAkGA1UEBhMCVVMxDjAM
;;; BgNVBBEMBTQ0NjA2MQ0wCwYDVQQIDARvaGlvMRQwEgYDVQQHDAtBcHBsZSBDcmVl
;;; azEVMBMGA1UECQwMMzQgTWFwbGUgU3QuMRIwEAYDVQQSDAlQT0JveCAxMDExETAP
;;; BgNVBAoMCE1hbnVTb2Z0MRQwEgYDVQQLDAtFbmdpbmVlcmluZzERMA8GA1UEAwwI
;;; TWFudVNvZnQwggEiMA0GCSqGSIb3DQEBAQUAA4IBDwAwggEKAoIBAQCjsVsAf9Bn
;;; 4tArwMyDl6a3MRqeM2J+DzjpGiuygsYKM0y1xVnU7fB7QUz/XxBaN3aXiJ8GPGpY
;;; accLwgSjQja/GU+bMz5fZ70Sk43jLVF0UATXt4Bj36V/hxbBTRswkrMpqoz70C3g
;;; 1uNkrpsvVP95Fy2C3tHdM7iJEflFU5d3PKi+OflkNDN2E2XkYInQZcnoWgi/hHLo
;;; dZKvA3WZ5O94iZtk78ug/IumwGWi+ALQurFEiAQMQHCDqDNXAk2+v/Wl3ioSNpWV
;;; cT/riwp11IXopY+mCkOmZglcYnc7D3/ry2yeCJ2TLv++VJtWxLy6lsUGic3L8vHg
;;; d/kyCvqd7JidAgMBAAGjggGuMIIBqjAfBgNVHSMEGDAWgBQpkWD/ik366/mmarjP
;;; +eZLvUnOEjAdBgNVHQ4EFgQUi0Hw/1VLGAwOYI5Ztfk5kCJKhhQwDgYDVR0PAQH/
;;; BAQDAgeAMAwGA1UdEwEB/wQCMAAwEwYDVR0lBAwwCgYIKwYBBQUHAwMwEQYJYIZI
;;; AYb4QgEBBAQDAgQQMEYGA1UdIAQ/MD0wOwYMKwYBBAGyMQECAQMCMCswKQYIKwYB
;;; BQUHAgEWHWh0dHBzOi8vc2VjdXJlLmNvbW9kby5uZXQvQ1BTMEMGA1UdHwQ8MDow
;;; OKA2oDSGMmh0dHA6Ly9jcmwuY29tb2RvY2EuY29tL0NPTU9ET1JTQUNvZGVTaWdu
;;; aW5nQ0EuY3JsMHQGCCsGAQUFBwEBBGgwZjA+BggrBgEFBQcwAoYyaHR0cDovL2Ny
;;; dC5jb21vZG9jYS5jb20vQ09NT0RPUlNBQ29kZVNpZ25pbmdDQS5jcnQwJAYIKwYB
;;; BQUHMAGGGGh0dHA6Ly9vY3NwLmNvbW9kb2NhLmNvbTAfBgNVHREEGDAWgRRzdXBw
;;; b3J0QG1hbnVzb2Z0LmNvbTANBgkqhkiG9w0BAQsFAAOCAQEAE2rS0S3ucoM/0xNM
;;; C7isOCd+ltT6ExWNqS1Sk7+W8UO911nQtYpovxk/h8imcF83mXlSGK0Kd5AnSC+L
;;; g78HkK7spHJxhiJDZOBtDcj+AYMknGBAeT5f0uGZaQchp7R3bNtK9YTsgF+N5ffM
;;; toqrxe77h2FG024PRpEJ0VusrKOJWOStaG06aLHdoebIc9k5wzXn/EIJzyWAksJB
;;; ziHpKt9ymkofHPoO/Nu8mGfW9Wv9eCRMdzo51fjuhIoi8vuKpFJOjrNzcxxk+1lZ
;;; 8MftGtgs1WjlypcjN+QYERiZg8sElhf1Yrylt/BGlCSjoPx3MVI6aAA7oVfKTphf
;;; oLBLWjGCAbwwggG4AgEBMIGQMH0xCzAJBgNVBAYTAkdCMRswGQYDVQQIExJHcmVh
;;; dGVyIE1hbmNoZXN0ZXIxEDAOBgNVBAcTB1NhbGZvcmQxGjAYBgNVBAoTEUNPTU9E
;;; TyBDQSBMaW1pdGVkMSMwIQYDVQQDExpDT01PRE8gUlNBIENvZGUgU2lnbmluZyBD
;;; QQIPJa78jzkg549/okqzon3RMA0GCSqGSIb3DQEBCwUAMA0GCSqGSIb3DQEBAQUA
;;; BIIBAAgGw0YGShG9wr1VLXvlMYqac1pcjBa9aZnFUx0IrLLAdLac/kTn1z47dYzg
;;; 5/kcb4eosxpavJi1gZ3lN9dQwHJAEnFTWHkwDegubpQiswrIWQU3V+oyb8m/SsP4
;;; CnfcSbzYloM/jI/vTJqIMzwMYjgaJmg172QXr3G7EuR/AFIaQ0IQbYxw8UvyYX7W
;;; I96Sz01qjkYF7+6pMan6RLH+zNgOz2ClFS+naC6pc3jmk2qVFFeEQdqeDoMJBVYo
;;; tYhrFdMMQZminvEN+JPpBzGiVjFqjwiOF9tcVQR9MuLlmPt7JcKGv9CLJ0QvCDlP
;;; vThGuhiu8Q62k63tprLMxOmrErA=
;;; gwgbUGA1UdDjGBrQSBqjgAMQA7ADMA
;;; LwAyADcALwAyADAAMQA1AC8ANAAvADUAOAAvADEALwBOAGEAdABpAG8AbgBhAGwA
;;; IABJAG4AcwB0AGkAdAB1AHQAZQAgAG8AZgAgAFMAdABhAG4AZABhAHIAZABzACAA
;;; YQBuAGQAIABUAGUAYwBoAG4AbwBsAG8AZwB5ACAAKAB0AGkAbQBlAC0AYQAuAG4A
;;; aQBzAHQALgBnAG8AdgApAAAA
;;; ;;; -----END-SIGNATURE-----
